module undeclared {
  yang-version 1.1;
  namespace "urn:undeclared";
  prefix undec;

  revision 2020-10-05;

  container foo {
    choice subnet {
      mandatory true;
      description
        "The subnet can be specified as a prefix length or,
         if the server supports non-contiguous netmasks, as
         a netmask.";
      leaf prefix-length {
        type uint8 {
          range "0..32";
        }
        description
          "The length of the subnet prefix.";
      }
      leaf netmask {
        type string;
        description
          "The subnet specified as a netmask.";
      }
    }
    description "contains choice with no case in it";
  }
}
