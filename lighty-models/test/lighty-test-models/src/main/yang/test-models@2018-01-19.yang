module test-models {
    yang-version 1;

    namespace "http://pantheon.tech/ns/test-models";

    prefix models;

    organization "PANTHEON.tech s.r.o.";

    description
        "Test models used for serialization and deserialization purposes and RESTCONF client testing

        Copyright (c) 2018-2021 PANTHEON.tech, s.r.o. and others.  All rights reserved.

        This program and the accompanying materials are made available under the
        terms of the Eclipse Public License v1.0 which accompanies this distribution,
        and is available at http://www.eclipse.org/legal/epl-v10.html";

    revision "2018-01-19" {
        description "Test models";
    }

    grouping container-group {
        container sample-container {
            description
                "This is a sample container used for serialization and deserialization";
            leaf name {
                type string;
            }
            leaf value {
                type uint32;
            }
        }
    }

    container choice-container {
        choice snack {
            case sports-arena {
                container inner-case {
                   uses container-group;
                   leaf foo {
                       type string;
                   }
                }
            }
            case late-night {
                leaf chocolate {
                    type enumeration {
                        enum dark;
                        enum milk;
                        enum first-available;
                    }
                }
            }
        }
    }

    container top-level-container {
        uses container-group;
    }

    container simple-container {
        description
            "Container without inner resources except leaves";
        leaf simple-string-leaf {
            type string;
        }
    }

    container container-with-list {
        list test-list {
            description
                "This is a sample list used for testing";
            key "test-name";

            leaf test-name {
                type string;
            }
            leaf test-value {
                type uint8;
            }
        }
    }

    list sample-list {
        description
            "This is a sample list used for testing";
        key "name";

        leaf name {
            type string;
        }

        leaf value {
            type uint8;
        }
    }

    rpc simple-input-output-rpc {
        description 
            "RPC with simple input and output";
        input {
            leaf input-obj {
                type string;
            }
        }
        output {
            leaf output-obj {
                type string;
            }
        }
    }

    rpc container-io-rpc {
        description
            "RPC with container input and output";
        input {
            uses container-group;
        }

        output {
            uses container-group;
        }
    }

}
