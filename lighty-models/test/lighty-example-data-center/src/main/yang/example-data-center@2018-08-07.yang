module example-data-center {
  yang-version 1.1;
  namespace "urn:example:data-center";
  prefix "sfarm";
  revision 2018-08-07;
  organization "PANTHEON.tech s.r.o.";

     description
        "Example of yang model for data center

        Copyright (c) 2021 PANTHEON.tech, s.r.o. and others.  All rights reserved.

        This program and the accompanying materials are made available under the
        terms of the Eclipse Public License v1.0 which accompanies this distribution,
        and is available at http://www.eclipse.org/legal/epl-v10.html";

  list server {
    key name;
    leaf name {
      type string;
    }
    action reset {
      input {
        leaf reset-at {
          type string;
          mandatory true;
        }
      }
      output {
        leaf reset-finished-at {
          type string;
          mandatory true;
        }
      }
    }
  }

  container device {
    action start {
      input {
        leaf start-at {
          type string;
          mandatory true;
        }
      }
      output {
        leaf start-finished-at {
          type string;
          mandatory true;
        }
      }
    }
  }

  container box-out {
    container box-in {
      action open {
      }
    }
  }
}
