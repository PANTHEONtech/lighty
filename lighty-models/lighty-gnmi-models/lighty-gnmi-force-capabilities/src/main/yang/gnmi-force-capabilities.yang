module gnmi-force-capabilities {
    yang-version 1;
    namespace "urn:lighty:gnmi:force:capabilities";
    prefix "gnmi-fc";

    description
        "Model used for rewriting capabilities provided from gNMI device.
         Schema contexts of gNMI node are constructed based on force-capability list.

         Copyright (c) 2021 PANTHEON.tech, s.r.o. and others.  All rights reserved.

         This program and the accompanying materials are made available under the
         terms of the Eclipse Public License v1.0 which accompanies this distribution,
         and is available at http://www.eclipse.org/legal/epl-v10.html";

    revision "2021-07-02" {
        description "Initial revision of gNMI force capabilities";
    }

    import network-topology { prefix nt; revision-date 2013-10-21; }
    import yang-ext { prefix ext; revision-date "2013-07-09";}
    import gnmi-topology { prefix gnmi; revision-date "2021-03-16";}
    import gnmi-yang-storage { prefix gnmi-ys; revision-date "2021-03-31";}

    grouping force-yang-models {
        list force-capability {
            description "List of capabilities that restrict the
                         use of the models. The client restricts the set of data
                         models to be used when interacting with the target.
                         The target must not utilize data tree elements that
                         are defined in schema modules outside the specified list
                         of capabilities.";
            key "name version";
            uses gnmi-ys:yang-model-name-version;
        }
    }

    augment "/nt:network-topology/nt:topology/nt:node/gnmi:extensions-parameters" {
        ext:augment-identifier "force-capabilities";

        uses force-yang-models;
    }
}
