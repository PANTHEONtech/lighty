module test-interfaces {

  yang-version "1";

  namespace "test:it";

  prefix "ti";

  description
    "Model used for testing purposes";

  container interfaces {
    leaf test-leaf {
        type string;
    }
  }
}
