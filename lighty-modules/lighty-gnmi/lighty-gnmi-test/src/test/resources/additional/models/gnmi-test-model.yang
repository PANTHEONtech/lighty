module gnmi-test-model {

  yang-version "1";
  namespace "test:model";
  prefix "gtm";

  import openconfig-extensions { prefix oc-ext; }
  import openconfig-inet-types { prefix inet; }
  import openconfig-aaa-types { prefix types; }

  oc-ext:openconfig-version "1.0.0";

  container test-data {
    leaf-list test-leaf-list {
      type string;
    }

    list test-list {
        key key;
        leaf key {
            type string;
        }
    }
    container nested-container {
        leaf nc-leaf {
            type string;
        }
    }
    list multiple-key-list {
      key "number leafref-key identityref-key union-key";
      leaf number {
        type inet:as-number;
      }
      leaf leafref-key {
        type leafref {
          path "../number";
        }
      }
      leaf identityref-key {
        type identityref {
          base "types:SYSTEM_DEFINED_ROLES";
        }
      }
      leaf union-key {
          type union {
            type int32;
            type enumeration {
              enum "unbounded";
            }
          }
        }
      container inner-container {
        leaf inner-data {
          type string;
        }
      }
    }
  }

  list base-list {
      key list-key;
      leaf list-key {
          type string;
      }

      list nested-list {
          key nested-list-key;
          leaf nested-list-key {
              type string;
          }
      }
  }

  augment /test-data {
      container augmented-container {
          leaf augmented-data {
              type string;
          }
      }
  }
}
