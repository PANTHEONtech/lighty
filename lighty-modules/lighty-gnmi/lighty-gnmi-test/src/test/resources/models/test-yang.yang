module test-yang {
    yang-version 1;
    namespace "test-yang";
    prefix "ty";

    description "Test model used for uploading model";

    revision "2021-05-18" {
        description "Initial revision of test model";
        reference "1.2.3";
    }

    container test-container {
        leaf test-leaf {
            type string;
        }
    }
}
