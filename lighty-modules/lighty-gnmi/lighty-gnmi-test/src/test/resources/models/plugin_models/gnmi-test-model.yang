module gnmi-test-model {

  yang-version "1";
  namespace "test:model";
  prefix "gtm";

  import openconfig-extensions { prefix oc-ext; }

  oc-ext:openconfig-version "1.0.0";

  container test-data {
    leaf-list test-leaf-list {
      type string;
    }

    list test-list {
        key key;
        leaf key {
            type string;
        }
    }
  }

  list base-list {
      key list-key;
      leaf list-key {
          type string;
      }

      list nested-list {
          key nested-list-key;
          leaf nested-list-key {
              type string;
          }
      }
  }
}
